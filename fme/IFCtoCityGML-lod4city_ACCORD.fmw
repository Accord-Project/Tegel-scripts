FME workspace IFCtoCityGML-lod4city_ACCORD.fmw

Parameters:
- SourceDataset_IFC = X:\Source\Project_Name.ifc   # Source Industry Foundation Class (IFC) File(s)
- DestDataset_CITYGML = X:\Source\Model_LOD4.gml   # Destination CityGML Document
- OutputFolder = G:\AG_GDI-HH\ACCORD\Beispieldaten Tegel Projekt\IFC\20240702_RevitModelleundIFC\2024-06-14-UC1 and UC2 - IFC 2x3 und IFC 4\test   # Select an output folder

Readers:
- IFC_2: IFC from $(SourceDataset_IFC) in EPSG:3068

Writers:
- CITYGML_2: CITYGML to $(DestDataset_CITYGML) in EPSG:25833

Note: To develop this workspace, the ifc-lod4city.fmw by Liz Sanderson from the article BIM to GIS (Intermediate) | IFC LOD 300 to LOD4CityGML example on the FME Support Center was used. / Source to download: BIM to GIS (Intermediate) | IFC LOD 300 to LOD 4 CityGML – FME Support Center / The reader and writer names, as well as the source files in this workspace (e.g., Project_Name.ifc), are fictitious and used for demonstration purposes only. / License agreement: Legal - Safe Software
GeometryPropertyExtractor
    EXTRACTTYPE_PARAM = Traits
    PREFIX_EXTRACTED_TRAITS = Yes
    EXTRACTED -> AttributeExposer
AttributeExposer
    ATTR_LIST = LongName,Name,ifc_unique_id,IfcSpace.CompositionType,IfcSpace.GlobalId,IfcSpace.ifc_instance_name,IfcSpace.ifc_property_set{0},IfcSpace.ifc_property_set{1},IfcSpace.ifc_property_set{2},IfcSpace.ifc_property_set{3},IfcSpace.ifc_property_set{4},IfcSpace.ifc_property_set{5},IfcSpace.ifc_property_set{6},IfcSpace.ifc_property_set{7},IfcSpace.ifc_property_set{8},IfcSpace.ifc_property_set{9},IfcSpace.ifc_property_set{10},IfcSpace.ifc_property_set{11},IfcSpace.ifc_property_set{12},IfcSpace.ifc_property_set{13},IfcSpace.ifc_property_set{14},IfcSpace.ifc_property_set{15},IfcSpace.ifc_property_set{16},IfcSpace.ifc_type_object_id,IfcSpace.ifc_unique_id,IfcSpace.LongName,IfcSpace.Name,IfcSpace.PredefinedType,"Pset_TXL_Raumliste_LOI Export for SP.Raumnutzung nach DIN277","Pset_TXL_Raumliste_LOI Export for SP.Ebene","Pset_TXL_Raumliste_LOI Export for SP.Lichte Höhe",Bemaßungen.Fläche,"Modelleigenschaften.Anforderungen Raumakustik","Modelleigenschaften.Anforderung Schallschutz","Modelleigenschaften.Anforderung Trittschallschutz","Bemaßungen.Höhe oben"
    -> ConvertGeometry_10
Junction_5
    -> Junction_6

Bookmark: BuildingFurniture
IfcBuildingElementProxy (reader IFC_2)
    attributes: GlobalId char(22), Name string, Description string, ObjectType string, Tag string, CompositionType enumeration
    -> ConvertGeometry_11
IfcFurnishingElement (reader IFC_2)
    attributes: GlobalId char(22), Name string, Description string, ObjectType string, Tag string
    -> ConvertGeometry_11
Note: Convert Geometry to / simple surface
ConvertGeometry_11
    IFC_UNIQUE_ID = @Value(ifc_unique_id)
    -> BinaryEncoder_9
Note: Get parent type
BinaryEncoder_9
    ATTR_TO_ENCODE = ifc_parent_unique_id
    DEST_ATTR = _parent_id
    ENCODING_TYPE = HEX
    -> VariableRetriever_8
VariableRetriever_8
    SCOPE = Global
    VALUE_ATTR = _parent_type
    VARNAME = t@Value(_parent_id)
    -> AttributeRenamer_9
Note: Set gml id
AttributeRenamer_9
    ATTR_TABLE:
      RENAME_SET_DEFAULT ifc_parent_unique_id > gml_parent_id
      RENAME_SET_DEFAULT ifc_unique_id > gml_id
    -> Tester_6
Note: Separate room items / from building items
Tester_6
    BOOL_OP = OR
    TEST_CLAUSE = TEST @Value(_parent_type) = IfcSpace
    TEST_MODE = TEST
    PASSED -> CityGMLGeometrySetter_3
    FAILED -> GetGrandParentID_9
Note: Set parent id
GetGrandParentID_9
    ATTR_TO_ENCODE = gml_parent_id
    DEST_ATTR = gml_parent_id
    -> CityGMLGeometrySetter_3
Note: Set LOD and role
CityGMLGeometrySetter_3
    GEOM = lod4MultiSurface
    ROLE = interiorFurniture
    -> NeighborFinder [BASE]
Note: AttributeRenamer_8 : Output
Junction_6
    -> AttributeRenamer_16
AttributeRenamer_16
    ATTR_TABLE = RENAME_SET_DEFAULT gml_id > gml_id_room
    -> NeighborFinder [CANDIDATE]
Note: Find Room-Id
NeighborFinder
    ATTR_ACCUM_MODE = Merge Candidate
    ATTR_CONFLICT_RES = Use Base
    CANDIDATES_FIRST = No
    INSERT_VERTEX = No
    K = 1
    MEASURES_FROM_CANDIDATE = Yes
    MEASURE_TYPE = Continuous
    MODE = Bases and Candidates
    TREAT_POLYGON_AS = Areas
    MATCHED -> AttributeManager_13
Note: Set link to Room
AttributeManager_13
    ATTR_TABLE = SET_TO gml_parent_id = @Value(gml_id_room)
    -> BuildingFurniture (writer CITYGML_2)
BuildingFurniture (writer CITYGML_2)
    attributes: citygml_feature_role xml_char(200), GlobalId xml_char(22), Name xml_buffer, Description xml_buffer, ObjectType xml_buffer, Tag xml_buffer, ifc_parent_id xml_buffer, CompositionType xml_buffer, _geometry_name xml_buffer, _parent_id xml_buffer, _parent_type xml_buffer, _gparent_id xml_buffer, gml_id_room xml_buffer, LongName xml_buffer, InteriorOrExteriorSpace xml_buffer, ElevationWithFlooring xml_real64, ifc_parent_unique_id xml_buffer, _distance xml_real64, _angle xml_real64, _candidate_angle xml_real64, _candidate_label_angle xml_real64, _closest_candidate_x xml_real64, _closest_candidate_y xml_real64, _closest_base_x xml_real64, _closest_base_y xml_real64, ifc_id xml_buffer, RoomUsageDIN277 xml_char(200), Level xml_char(200), FloorHeight xml_char(200), RoomArea xml_char(200),
      BuildingHeight xml_char(200), NoiseProtection xml_char(200), FootfallNoiseProtection xml_char(200), RoomAcoustic xml_char(200), IfcSpace.CompositionType xml_char(200), IfcSpace.GlobalId xml_char(200), IfcSpace.ifc_instance_name xml_char(200), IfcSpace.ifc_property_set{0} xml_char(200), IfcSpace.ifc_property_set{1} xml_char(200), IfcSpace.ifc_property_set{2} xml_char(200), IfcSpace.ifc_property_set{3} xml_char(200), IfcSpace.ifc_property_set{4} xml_char(200), IfcSpace.ifc_property_set{5} xml_char(200), IfcSpace.ifc_property_set{6} xml_char(200), IfcSpace.ifc_property_set{7} xml_char(200), IfcSpace.ifc_property_set{8} xml_char(200), IfcSpace.ifc_property_set{9} xml_char(200), IfcSpace.ifc_property_set{10} xml_char(200), IfcSpace.ifc_property_set{11} xml_char(200), IfcSpace.ifc_property_set{12} xml_char(200), IfcSpace.ifc_property_set{13} xml_char(200), IfcSpace.ifc_property_set{14} xml_char(200), IfcSpace.ifc_property_set{15} xml_char(200), IfcSpace.ifc_property_set{16} xml_char(200), IfcSpace.ifc_type_object_id xml_char(200), IfcSpace.ifc_unique_id xml_char(200), IfcSpace.LongName xml_char(200), IfcSpace.Name xml_char(200), IfcSpace.PredefinedType xml_char(200)

Bookmark: CityModel
IfcProject (reader IFC_2)
    attributes: GlobalId char(22), Name string, Description string, ObjectType string, LongName string, Phase string
    -> AttributeRenamer_14
Note: Set gml_id
AttributeRenamer_14
    ATTR_TABLE:
      RENAME_SET_DEFAULT ifc_unique_id > gml_id
      RENAME_SET_DEFAULT Name > gml_name
      RENAME_SET_DEFAULT Description > gml_description
    -> AttributeManager_2
Note: Rename gml_id
AttributeManager_2
    ATTR_TABLE = SET_TO gml_id = CityModel
    -> CityModel (writer CITYGML_2)
CityModel (writer CITYGML_2)
    attributes: name xml_char(200), description xml_char(200), GlobalId xml_char(22), ObjectType xml_buffer, LongName xml_buffer, Phase xml_buffer, ifc_parent_unique_id xml_buffer, ifc_parent_id xml_buffer, gml_name xml_buffer, gml_description xml_buffer, ifc_id xml_buffer

Bookmark: Building
IfcBuilding (reader IFC_2)
    attributes: GlobalId char(22), Name string, Description string, ObjectType string, LongName string, CompositionType string, ElevationOfRefHeight real, ElevationOfTerrain real, BuildingAddress.Purpose enumeration, BuildingAddress.Description string, BuildingAddress.UserDefinedPurpose string, BuildingAddress.InternalLocation string, BuildingAddress.AddressLines string, BuildingAddress.PostalBox string, BuildingAddress.Town string, BuildingAddress.Region string, BuildingAddress.PostalCode string, BuildingAddress.Country string
    -> GeometryRemover
Note: Remove Geometry
GeometryRemover
    REMOVE_COORDSYS = No
    -> AttributeRenamer_12
Note: Set gml_id
AttributeRenamer_12
    ATTR_TABLE:
      RENAME_SET_DEFAULT ifc_unique_id > gml_id
      RENAME_SET_DEFAULT ifc_parent_unique_id > gml_parent_id
    -> AttributeManager_3
Note: Set link to CityModel, rename gml_id
AttributeManager_3
    ATTR_TABLE:
      SET_TO gml_id = Building
      SET_TO gml_parent_id = CityModel
    -> Building (writer CITYGML_2)
Note: Building
Building (writer CITYGML_2)
    attributes: GlobalId xml_char(22), Name xml_buffer, Description xml_buffer, ObjectType xml_buffer, LongName xml_buffer, CompositionType xml_buffer, ElevationOfRefHeight xml_real64, ElevationOfTerrain xml_real64, BuildingAddress.Purpose xml_buffer, BuildingAddress.Description xml_buffer, BuildingAddress.UserDefinedPurpose xml_buffer, BuildingAddress.InternalLocation xml_buffer, BuildingAddress.AddressLines xml_buffer, BuildingAddress.PostalBox xml_buffer, BuildingAddress.Town xml_buffer, BuildingAddress.Region xml_buffer, BuildingAddress.PostalCode xml_buffer, BuildingAddress.Country xml_buffer, ifc_parent_id xml_buffer

Bookmark: Room
IfcSpace (reader IFC_2)
    attributes: GlobalId char(22), Name string, Description string, ObjectType string, LongName string, CompositionType enumeration, InteriorOrExteriorSpace enumeration, ElevationWithFlooring real
    -> GeometryPropertyExtractor
Note: Convert Geometry to / simple surface
ConvertGeometry_10
    IFC_UNIQUE_ID = @Value(ifc_unique_id)
    -> AttributeRenamer_8
Note: Set gml id
AttributeRenamer_8
    ATTR_TABLE:
      RENAME_SET_DEFAULT ifc_unique_id > gml_id
      RENAME_SET_DEFAULT Pset_TXL_Raumliste_LOI Export for SP.Raumnutzung nach DIN277 > RoomUsageDIN277
      RENAME_SET_DEFAULT Pset_TXL_Raumliste_LOI Export for SP.Ebene > Level
      RENAME_SET_DEFAULT Pset_TXL_Raumliste_LOI Export for SP.Lichte Höhe > FloorHeight
      RENAME_SET_DEFAULT Bemaßungen.Fläche > RoomArea
      RENAME_SET_DEFAULT Bemaßungen.Höhe oben > BuildingHeight
      RENAME_SET_DEFAULT Modelleigenschaften.Anforderung Schallschutz > NoiseProtection
      RENAME_SET_DEFAULT Modelleigenschaften.Anforderung Trittschallschutz > FootfallNoiseProtection
      RENAME_SET_DEFAULT Modelleigenschaften.Anforderungen Raumakustik > RoomAcoustic
    -> GetGrandParentID_8
    -> Junction_5
Note: AttributeRenamer_16 : Input
Note: Set parent id
GetGrandParentID_8
    ATTR_TO_ENCODE = ifc_parent_unique_id
    DEST_ATTR = gml_parent_id
    -> CityGMLGeometrySetter_2
Note: Set LOD and role
CityGMLGeometrySetter_2
    GEOM = lod4MultiSurface
    ROLE = interiorRoom
    -> AttributeManager_5
Note: Set link to Building
AttributeManager_5
    ATTR_TABLE = SET_TO gml_parent_id = Building
    -> Room (writer CITYGML_2)
Room (writer CITYGML_2)
    attributes: citygml_feature_role xml_char(200), GlobalId xml_char(22), Name xml_buffer, Description xml_buffer, ObjectType xml_buffer, LongName xml_buffer, CompositionType xml_buffer, InteriorOrExteriorSpace xml_buffer, ElevationWithFlooring xml_real64, ifc_parent_unique_id xml_buffer, ifc_parent_id xml_buffer, _geometry_name xml_buffer, _parent_id xml_buffer, _gparent_id xml_buffer, ifc_id xml_buffer, IfcSpace.CompositionType xml_char(200), IfcSpace.GlobalId xml_char(200), IfcSpace.ifc_instance_name xml_char(200), IfcSpace.ifc_property_set{0} xml_char(200), IfcSpace.ifc_property_set{1} xml_char(200), IfcSpace.ifc_property_set{2} xml_char(200), IfcSpace.ifc_property_set{3} xml_char(200), IfcSpace.ifc_property_set{4} xml_char(200), IfcSpace.ifc_property_set{5} xml_char(200), IfcSpace.ifc_property_set{6} xml_char(200), IfcSpace.ifc_property_set{7} xml_char(200), IfcSpace.ifc_property_set{8} xml_char(200), IfcSpace.ifc_property_set{9} xml_char(200), IfcSpace.ifc_property_set{10} xml_char(200), IfcSpace.ifc_property_set{11} xml_char(200),
      IfcSpace.ifc_property_set{12} xml_char(200), IfcSpace.ifc_property_set{13} xml_char(200), IfcSpace.ifc_property_set{14} xml_char(200), IfcSpace.ifc_property_set{15} xml_char(200), IfcSpace.ifc_property_set{16} xml_char(200), IfcSpace.ifc_type_object_id xml_char(200), IfcSpace.ifc_unique_id xml_char(200), IfcSpace.LongName xml_char(200), IfcSpace.Name xml_char(200), IfcSpace.PredefinedType xml_char(200), IfcSpace.ifc_property_set{} xml_char(200), Level xml_char(200), FloorHeight xml_int32, RoomArea xml_int32, RoomUsageDIN277 xml_char(200), BuildingHeight xml_int32, NoiseProtection xml_char(200), FootfallNoiseProtection xml_char(200), RoomAcoustic xml_char(200)

Bookmark: BuildingPart
IfcBuildingStorey (reader IFC_2)
    attributes: GlobalId char(22), Name string, Description string, ObjectType string, LongName string, CompositionType enumeration, Elevation real
    -> GeometryRemover_3
Note: Remove Geometry
GeometryRemover_3
    REMOVE_COORDSYS = No
    -> AttributeRenamer_15
Note: Set gml id
AttributeRenamer_15
    ATTR_TABLE:
      RENAME_SET_DEFAULT ifc_parent_unique_id > gml_parent_id
      RENAME_SET_DEFAULT ifc_unique_id > gml_id
    -> AttributeManager_4
Note: Set link to Building
AttributeManager_4
    ATTR_TABLE = SET_TO gml_parent_id = Building
    -> BuildingPart (writer CITYGML_2)
IfcCovering (reader IFC_2)
    attributes: GlobalId char(22), Name string, Description string, ObjectType string, Tag varchar(255), PredefinedType enumeration, Axis geometry, Body geometry, Box geometry, FootPrint geometry, ifc_property_set{} string, ifc_quantity_set{} string, ifc_type_object_id string
    -> ConvertGeometry_13
IfcFooting (reader IFC_2)
    attributes: GlobalId char(22), Name string, Description string, ObjectType string, Tag string, PredefinedType enumeration
    -> ConvertGeometry_13
Note: Convert Geometry to / simple surface
ConvertGeometry_13
    IFC_UNIQUE_ID = @Value(ifc_unique_id)
    -> AttributeRenamer_11
Note: Set gml id
AttributeRenamer_11
    ATTR_TABLE:
      RENAME_SET_DEFAULT ifc_parent_unique_id > gml_parent_id
      RENAME_SET_DEFAULT ifc_unique_id > gml_id
    -> GetGrandParentID_11
Note: Set parent id
GetGrandParentID_11
    ATTR_TO_ENCODE = gml_parent_id
    DEST_ATTR = gml_parent_id
    -> CityGMLGeometrySetter_8
Note: Set LOD and role
CityGMLGeometrySetter_8
    GEOM = lod4MultiSurface
    ROLE = consistsOfBuildingPart
    -> AttributeManager_6
Note: Set link to Building
AttributeManager_6
    ATTR_TABLE = SET_TO gml_parent_id = Building
    -> BuildingPart (writer CITYGML_2)
BuildingPart (writer CITYGML_2)
    attributes: GlobalId xml_char(22), Name xml_buffer, Description xml_buffer, ObjectType xml_buffer, LongName xml_buffer, CompositionType xml_buffer, Elevation xml_real64, ifc_parent_id xml_buffer, ifc_id xml_buffer, citygml_feature_role xml_char(200), Tag xml_buffer, PredefinedType xml_buffer, Axis xml_buffer, Body xml_buffer, Box xml_buffer, FootPrint xml_buffer, ifc_property_set{} xml_buffer, ifc_quantity_set{} xml_buffer, ifc_type_object_id xml_buffer, _geometry_name xml_buffer, _parent_id xml_buffer, _gparent_id xml_buffer

Bookmark: Window
IfcPlate (reader IFC_2)
    attributes: GlobalId char(22), Name string, Description string, ObjectType string, Tag string
    -> ConvertGeometry_2
Note: Convert Geometry to / simple surface
ConvertGeometry_2
    IFC_UNIQUE_ID = @Value(ifc_unique_id)
    -> AttributeRenamer
Note: Set gml id
AttributeRenamer
    ATTR_TABLE:
      RENAME_SET_DEFAULT ifc_parent_unique_id > gml_parent_id
      RENAME_SET_DEFAULT ifc_unique_id > gml_id
    -> CityGMLGeometrySetter_7
IfcWindow (reader IFC_2)
    attributes: GlobalId char(22), Name string, Description string, ObjectType string, Tag string, OverallHeight real, OverallWidth real
    -> ConvertGeometry_4
ConvertGeometry_4
    IFC_UNIQUE_ID = @Value(ifc_unique_id)
    -> AttributeRenamer_2
AttributeRenamer_2
    ATTR_TABLE = RENAME_SET_DEFAULT ifc_unique_id > gml_id
    -> GetGrandParentID_2
Note: Set parent id
GetGrandParentID_2
    ATTR_TO_ENCODE = ifc_parent_unique_id
    DEST_ATTR = gml_parent_id
    -> CityGMLGeometrySetter_7
Note: Set LOD and role
CityGMLGeometrySetter_7
    GEOM = lod4MultiSurface
    ROLE = opening
    -> NeighborFinder_3 [BASE]
Note: AttributeRenamer_4 : Output
Junction_8
    -> AttributeRenamer_5
AttributeRenamer_5
    ATTR_TABLE = RENAME_SET_DEFAULT gml_id > gml_id_wall
    -> NeighborFinder_3 [CANDIDATE]
Note: Find Walll-Id
NeighborFinder_3
    ATTR_ACCUM_MODE = Merge Candidate
    ATTR_CONFLICT_RES = Use Base
    CANDIDATES_FIRST = No
    INSERT_VERTEX = No
    K = 1
    MEASURES_FROM_CANDIDATE = Yes
    MEASURE_TYPE = Continuous
    MODE = Bases and Candidates
    TREAT_POLYGON_AS = Areas
    MATCHED -> AttributeManager
Note: Set link to Walll
AttributeManager
    ATTR_TABLE = SET_TO gml_parent_id = @Value(gml_id_wall)
    -> Window (writer CITYGML_2)
Window (writer CITYGML_2)
    attributes: citygml_feature_role xml_char(200), GlobalId xml_char(22), Name xml_buffer, Description xml_buffer, ObjectType xml_buffer, Tag xml_buffer, ifc_parent_id xml_buffer, _geometry_name xml_buffer, OverallHeight xml_real64, OverallWidth xml_real64, ifc_parent_unique_id xml_buffer, _parent_id xml_buffer, _gparent_id xml_buffer, gml_id_wall xml_buffer, _distance xml_real64, _angle xml_real64, _candidate_angle xml_real64, _candidate_label_angle xml_real64, _closest_candidate_x xml_real64, _closest_candidate_y xml_real64, _closest_base_x xml_real64, _closest_base_y xml_real64, ifc_id xml_buffer

Bookmark: IntBuildingInstallation
IfcFlowTerminal (reader IFC_2)
    attributes: GlobalId char(22), Name string, Description string, ObjectType string, Tag string
    -> ConvertGeometry_12
Note: Convert Geometry to / simple surface
ConvertGeometry_12
    IFC_UNIQUE_ID = @Value(ifc_unique_id)
    -> BinaryEncoder_10
Note: Get parent type
BinaryEncoder_10
    ATTR_TO_ENCODE = ifc_parent_unique_id
    DEST_ATTR = _parent_id
    ENCODING_TYPE = HEX
    -> VariableRetriever_9
VariableRetriever_9
    SCOPE = Global
    VALUE_ATTR = _parent_type
    VARNAME = t@Value(_parent_id)
    -> AttributeRenamer_10
Note: Set gml id
AttributeRenamer_10
    ATTR_TABLE:
      RENAME_SET_DEFAULT ifc_parent_unique_id > gml_parent_id
      RENAME_SET_DEFAULT ifc_unique_id > gml_id
    -> Tester_7
Note: Separate room items / from building items
Tester_7
    BOOL_OP = OR
    TEST_CLAUSE = TEST @Value(_parent_type) = IfcSpace
    TEST_MODE = TEST
    PASSED -> CityGMLGeometrySetter_11
    FAILED -> GetGrandParentID_10
Note: Set LOD and role
CityGMLGeometrySetter_11
    GEOM = lod4MultiSurface
    ROLE = roomInstallation
    -> AttributeManager_7
Note: Set parent id
GetGrandParentID_10
    ATTR_TO_ENCODE = gml_parent_id
    DEST_ATTR = gml_parent_id
    -> CityGMLGeometrySetter_12
CityGMLGeometrySetter_12
    GEOM = lod4MultiSurface
    ROLE = interiorBuildingInstallation
    -> AttributeManager_7
Note: Set link to Building
AttributeManager_7
    ATTR_TABLE = SET_TO gml_parent_id = Building
    -> IntBuildingInstallation (writer CITYGML_2)
Note: CityGMLGeometrySetter_10 : OUTPUT
Junction_4
    -> IntBuildingInstallation (writer CITYGML_2)
IntBuildingInstallation (writer CITYGML_2)
    attributes: citygml_feature_role xml_char(200), GlobalId xml_char(22), Name xml_buffer, Description xml_buffer, ObjectType xml_buffer, Tag xml_buffer, ShapeType xml_buffer, ifc_parent_unique_id xml_buffer, ifc_parent_id xml_buffer, _parent_id xml_buffer, _parent_type xml_buffer, _geometry_name xml_buffer, PredefinedType xml_buffer, _gparent_id xml_buffer, ifc_id xml_buffer, ifc_unique_id xml_buffer, Axis xml_buffer, Body xml_buffer, Box xml_buffer, FootPrint xml_buffer, ifc_property_set{} xml_buffer, ifc_quantity_set{} xml_buffer, ifc_type_object_id xml_buffer

Bookmark: Door
IfcDoor (reader IFC_2)
    attributes: GlobalId char(22), Name string, Description string, ObjectType string, Tag string, OverallHeight real, OverallWidth real
    -> ConvertGeometry_5
Note: Convert Geometry to / simple surface
ConvertGeometry_5
    IFC_UNIQUE_ID = @Value(ifc_unique_id)
    -> BinaryEncoder_4
Note: Get parent type
BinaryEncoder_4
    ATTR_TO_ENCODE = ifc_parent_unique_id
    DEST_ATTR = _parent_id
    ENCODING_TYPE = HEX
    -> VariableRetriever_3
VariableRetriever_3
    SCOPE = Global
    VALUE_ATTR = _parent_type
    VARNAME = t@Value(_parent_id)
    -> AttributeRenamer_13
Note: Set gml id
AttributeRenamer_13
    ATTR_TABLE:
      RENAME_SET_DEFAULT ifc_parent_unique_id > gml_parent_id
      RENAME_SET_DEFAULT ifc_unique_id > gml_id
    -> Tester_2
Note: Separate wall doors from / curtain wall doors
Tester_2
    BOOL_OP = OR
    TEST_CLAUSE = TEST @Value(_parent_type) NOT_= IfcCurtainWall
    TEST_MODE = TEST
    PASSED -> GetGrandParentID
    FAILED -> CityGMLGeometrySetter_6
Note: Set parent id
GetGrandParentID
    ATTR_TO_ENCODE = gml_parent_id
    DEST_ATTR = gml_parent_id
    -> CityGMLGeometrySetter_6
Note: Set LOD and role
CityGMLGeometrySetter_6
    GEOM = lod4MultiSurface
    ROLE = opening
    -> NeighborFinder_2 [BASE]
Note: AttributeRenamer_4 : Output
Junction_7
    -> AttributeRenamer_17
AttributeRenamer_17
    ATTR_TABLE = RENAME_SET_DEFAULT gml_id > gml_id_wall
    -> NeighborFinder_2 [CANDIDATE]
Note: Find Wall-Id
NeighborFinder_2
    ATTR_ACCUM_MODE = Merge Candidate
    ATTR_CONFLICT_RES = Use Base
    CANDIDATES_FIRST = No
    INSERT_VERTEX = No
    K = 1
    MEASURES_FROM_CANDIDATE = Yes
    MEASURE_TYPE = Continuous
    MODE = Bases and Candidates
    TREAT_POLYGON_AS = Areas
    MATCHED -> AttributeManager_14
Note: Set link to Wall
AttributeManager_14
    ATTR_TABLE = SET_TO gml_parent_id = @Value(gml_id_wall)
    -> Door (writer CITYGML_2)
Door (writer CITYGML_2)
    attributes: citygml_feature_role xml_char(200), GlobalId xml_char(22), Name xml_buffer, Description xml_buffer, ObjectType xml_buffer, Tag xml_buffer, OverallHeight xml_real64, OverallWidth xml_real64, ifc_parent_id xml_buffer, _geometry_name xml_buffer, _parent_id xml_buffer, _parent_type xml_buffer, _gparent_id xml_buffer, gml_id_wall xml_buffer, ifc_parent_unique_id xml_buffer, _distance xml_real64, _angle xml_real64, _candidate_angle xml_real64, _candidate_label_angle xml_real64, _closest_candidate_x xml_real64, _closest_candidate_y xml_real64, _closest_base_x xml_real64, _closest_base_y xml_real64, ifc_id xml_buffer

Bookmark: Roof and Floor
IfcRoof (reader IFC_2)
    attributes: GlobalId char(22), Name string, Description string, ObjectType string, Tag string, ShapeType enumeration
    -> ConvertGeometry_14
Note: Convert Geometry to / simple surface
ConvertGeometry_14
    IFC_UNIQUE_ID = @Value(ifc_unique_id)
    -> BinaryEncoder_11
Note: Get parent type
BinaryEncoder_11
    ATTR_TO_ENCODE = ifc_parent_unique_id
    DEST_ATTR = _parent_id
    ENCODING_TYPE = HEX
    -> VariableRetriever_10
VariableRetriever_10
    SCOPE = Global
    VALUE_ATTR = _parent_type
    VARNAME = t@Value(_parent_id)
    -> AttributeRenamer_7
Note: Set gml id
AttributeRenamer_7
    ATTR_TABLE = RENAME_SET_DEFAULT ifc_unique_id > gml_id
    -> FeatureMerger_2 [REQUESTOR]
IfcSlab (reader IFC_2)
    attributes: GlobalId char(22), Name string, Description string, ObjectType string, Tag string, PredefinedType enumeration
    -> ConvertGeometry_6
Note: Convert Geometry to / simple surface
ConvertGeometry_6
    IFC_UNIQUE_ID = @Value(ifc_unique_id)
    -> BinaryEncoder_5
Note: Get parent type
BinaryEncoder_5
    ATTR_TO_ENCODE = ifc_parent_unique_id
    DEST_ATTR = _parent_id
    ENCODING_TYPE = HEX
    -> VariableRetriever_4
VariableRetriever_4
    SCOPE = Global
    VALUE_ATTR = _parent_type
    VARNAME = t@Value(_parent_id)
    -> AttributeFilter
Note: Routeto appropriate parent
AttributeFilter
    ATTR_NAME = _parent_type
    ATTR_VALUES = <Empty>,<Missing>,<Null>,<Unfiltered>,IfcRoof,IfcStair
    <UNFILTERED> -> AttributeRenamer_6
    IfcRoof -> FeatureMerger_2 [SUPPLIER]
    IfcStair -> FeatureMerger_3 [SUPPLIER]
Note: Add roof slab geometry onto roof
FeatureMerger_2
    JOIN_KEYS = @Value(gml_id) @Value(ifc_parent_unique_id) AUTO
    MERGE_TYPE = Geometry
    PROCESS_DUPS = NO
    REJECT_NULL_MISSING_KEYS = No
    SUPPLIERS_FIRST = No
    MERGED -> GetGrandParentID_5
    UNMERGED_REQUESTOR -> GetGrandParentID_5
Note: Set parent id
GetGrandParentID_5
    ATTR_TO_ENCODE = ifc_parent_unique_id
    DEST_ATTR = gml_parent_id
    -> CityGMLGeometrySetter
Note: Set LOD and role
CityGMLGeometrySetter
    GEOM = lod4MultiSurface
    ROLE = boundedBy
    -> AttributeManager_9
Note: Set link to Building
AttributeManager_9
    ATTR_TABLE = SET_TO gml_parent_id = Building
    -> RoofSurface (writer CITYGML_2)
RoofSurface (writer CITYGML_2)
    attributes: citygml_feature_role xml_char(200), GlobalId xml_char(22), Name xml_buffer, Description xml_buffer, ObjectType xml_buffer, Tag xml_buffer, ShapeType xml_buffer, ifc_parent_unique_id xml_buffer, ifc_parent_id xml_buffer, _geometry_name xml_buffer, _parent_id xml_buffer, _parent_type xml_buffer, _gparent_id xml_buffer, ifc_id xml_buffer
Note: Set gml id
AttributeRenamer_6
    ATTR_TABLE = RENAME_SET_DEFAULT ifc_unique_id > gml_id
    -> GetGrandParentID_4
Note: Set parent id
GetGrandParentID_4
    ATTR_TO_ENCODE = ifc_parent_unique_id
    DEST_ATTR = gml_parent_id
    -> CityGMLGeometrySetter_4
Note: Set LOD and role
CityGMLGeometrySetter_4
    GEOM = lod4MultiSurface
    ROLE = boundedBy
    -> AttributeManager_10
Note: Set link to Building
AttributeManager_10
    ATTR_TABLE = SET_TO gml_parent_id = Building
    -> FloorSurface (writer CITYGML_2)
FloorSurface (writer CITYGML_2)
    attributes: citygml_feature_role xml_char(200), GlobalId xml_char(22), Name xml_buffer, Description xml_buffer, ObjectType xml_buffer, Tag xml_buffer, PredefinedType xml_buffer, ifc_parent_unique_id xml_buffer, ifc_parent_id xml_buffer, _geometry_name xml_buffer, _parent_id xml_buffer, _parent_type xml_buffer, _gparent_id xml_buffer, ifc_id xml_buffer

Bookmark: BuildingInstallation
IfcColumn (reader IFC_2)
    attributes: GlobalId char(22), Name string, Description string, ObjectType string, Tag string
    -> ConvertGeometry_7
IfcBeam (reader IFC_2)
    attributes: GlobalId char(22), Name string, Description string, ObjectType string, Tag string
    -> ConvertGeometry_7
Note: Convert Geometry to / simple surface
ConvertGeometry_7
    IFC_UNIQUE_ID = @Value(ifc_unique_id)
    -> BinaryEncoder_6
Note: Get parent type
BinaryEncoder_6
    ATTR_TO_ENCODE = ifc_parent_unique_id
    DEST_ATTR = _parent_id
    ENCODING_TYPE = HEX
    -> VariableRetriever_5
VariableRetriever_5
    SCOPE = Global
    VALUE_ATTR = _parent_type
    VARNAME = t@Value(_parent_id)
    -> Tester_4
IfcRailing (reader IFC_2)
    attributes: GlobalId char(22), Name string, Description string, ObjectType string, Tag string, PredefinedType enumeration
    -> ConvertGeometry_8
ConvertGeometry_8
    IFC_UNIQUE_ID = @Value(ifc_unique_id)
    -> BinaryEncoder_7
BinaryEncoder_7
    ATTR_TO_ENCODE = ifc_parent_unique_id
    DEST_ATTR = _parent_id
    ENCODING_TYPE = HEX
    -> VariableRetriever_6
VariableRetriever_6
    SCOPE = Global
    VALUE_ATTR = _parent_type
    VARNAME = t@Value(_parent_id)
    -> Tester_5
Note: Separate stair railings / from builiding railings
Tester_5
    BOOL_OP = OR
    TEST_CLAUSE = TEST @Value(_parent_type) = IfcStair
    TEST_MODE = TEST
    PASSED -> FeatureMerger_3 [SUPPLIER]
    FAILED -> Tester_4
Note: Part of assembly?
Tester_4
    BOOL_OP = OR
    TEST_CLAUSE = TEST @Value(_parent_type) = IfcElementAssembly
    TEST_MODE = TEST
    PASSED -> GetGrandParentID_6
    FAILED -> AttributeRenamer_3
Note: Get interim parent
GetGrandParentID_6
    ATTR_TO_ENCODE = ifc_parent_unique_id
    DEST_ATTR = gml_parent_id
    -> AttributeRenamer_3
IfcStairFlight (reader IFC_2)
    attributes: GlobalId char(22), Name string, Description string, ObjectType string, Tag string, NumberOfRiser int, NumberOfTreads int, RiserHeight real, TreadLength real
    -> ConvertGeometry_9
ConvertGeometry_9
    IFC_UNIQUE_ID = @Value(ifc_unique_id)
    -> FeatureMerger_3 [SUPPLIER]
Note: Add part geometry to Stair
IfcStair (reader IFC_2)
    attributes: GlobalId char(22), Name string, Description string, ObjectType string, Tag string, ShapeType enumeration
    -> FeatureMerger_3 [REQUESTOR]
FeatureMerger_3
    GEOM_TYPE = Build Aggregates
    JOIN_KEYS = @Value(ifc_unique_id) @Value(ifc_parent_unique_id) AUTO
    MERGE_TYPE = Geometry
    PROCESS_DUPS = YES
    REJECT_NULL_MISSING_KEYS = No
    SUPPLIERS_FIRST = No
    MERGED -> BinaryEncoder_8
Note: Get parent type
BinaryEncoder_8
    ATTR_TO_ENCODE = ifc_parent_unique_id
    DEST_ATTR = _parent_id
    ENCODING_TYPE = HEX
    -> VariableRetriever_7
VariableRetriever_7
    SCOPE = Global
    VALUE_ATTR = _parent_type
    VARNAME = t@Value(_parent_id)
    -> AttributeRenamer_3
Note: Set gml id
AttributeRenamer_3
    ATTR_TABLE = RENAME_SET_DEFAULT ifc_unique_id > gml_id
    -> GetGrandParentID_7
Note: Set parent id
GetGrandParentID_7
    ATTR_TO_ENCODE = gml_parent_id
    DEST_ATTR = gml_parent_id
    -> CityGMLGeometrySetter_10
Note: Set LOD and role
CityGMLGeometrySetter_10
    GEOM = lod4MultiSurface
    ROLE = interiorBuildingInstallation
    -> AttributeManager_11
IfcRampFlight (reader IFC_2)
    attributes: GlobalId char(22), Name string, Description string, ObjectType string, Tag varchar(255), PredefinedType enumeration, Axis geometry, Body geometry, Box geometry, FootPrint geometry, ifc_property_set{} string, ifc_quantity_set{} string, ifc_type_object_id string
    -> ConvertGeometry_15
ConvertGeometry_15
    IFC_UNIQUE_ID = @Value(ifc_unique_id)
    -> AttributeManager_11
Note: Set link to Building
AttributeManager_11
    ATTR_TABLE = SET_TO gml_parent_id = Building
    -> Junction_3
Note: IntBuildingInstallation
Junction_3
    -> Junction_4

Bookmark: WallSurface
IfcMember (reader IFC_2)
    attributes: GlobalId char(22), Name string, Description string, ObjectType string, Tag string
    -> ConvertGeometry_3
Note: Convert Geometry to / simple surface
ConvertGeometry_3
    IFC_UNIQUE_ID = @Value(ifc_unique_id)
    -> BinaryEncoder_3
Note: Get parent type
BinaryEncoder_3
    ATTR_TO_ENCODE = ifc_parent_unique_id
    DEST_ATTR = _parent_id
    ENCODING_TYPE = HEX
    -> VariableRetriever_2
VariableRetriever_2
    SCOPE = Global
    VALUE_ATTR = _parent_type
    VARNAME = t@Value(_parent_id)
    -> Tester
Note: Separate curtain wall memebrs / from Stair members
Tester
    BOOL_OP = OR
    TEST_CLAUSE = TEST @Value(_parent_type) = IfcCurtainWall
    TEST_MODE = TEST
    PASSED -> FeatureMerger [SUPPLIER]
    FAILED -> FeatureMerger_3 [SUPPLIER]
IfcWallStandardCase (reader IFC_2)
    attributes: GlobalId char(22), Name string, Description string, ObjectType string, Tag string
    -> ConvertGeometry
IfcWall (reader IFC_2)
    attributes: GlobalId char(22), Name string, Description string, ObjectType string, Tag string
    -> ConvertGeometry
ConvertGeometry
    IFC_UNIQUE_ID = @Value(ifc_unique_id)
    -> AttributeRenamer_4
Note: Add member geometry to curtain wall
IfcCurtainWall (reader IFC_2)
    attributes: GlobalId char(22), Name string, Description string, ObjectType string, Tag string
    -> FeatureMerger [REQUESTOR]
FeatureMerger
    GEOM_TYPE = Build Aggregates
    JOIN_KEYS = @Value(ifc_unique_id) @Value(ifc_parent_unique_id) AUTO
    MERGE_TYPE = Geometry
    PROCESS_DUPS = YES
    REJECT_NULL_MISSING_KEYS = No
    SUPPLIERS_FIRST = No
    MERGED -> AttributeRenamer_4
Note: Set gml id
AttributeRenamer_4
    ATTR_TABLE = RENAME_SET_DEFAULT ifc_unique_id > gml_id
    -> GetGrandParentID_3
    -> Junction_2
    -> Junction
Note: Set parent id
GetGrandParentID_3
    ATTR_TO_ENCODE = ifc_parent_unique_id
    DEST_ATTR = gml_parent_id
    -> CityGMLGeometrySetter_5
Note: Set LOD and role
CityGMLGeometrySetter_5
    GEOM = lod4MultiSurface
    ROLE = boundedBy
    -> AttributeManager_12
Note: Set link to Building
AttributeManager_12
    ATTR_TABLE = SET_TO gml_parent_id = Building
    -> WallSurface (writer CITYGML_2)
WallSurface (writer CITYGML_2)
    attributes: citygml_feature_role xml_char(200), GlobalId xml_char(22), Name xml_buffer, Description xml_buffer, ObjectType xml_buffer, Tag xml_buffer, ifc_parent_unique_id xml_buffer, ifc_parent_id xml_buffer, _geometry_name xml_buffer, _parent_id xml_buffer, _gparent_id xml_buffer, ifc_id xml_buffer
Note: AttributeRenamer_5 : Input
Junction
    -> Junction_8
Note: AttributeRenamer_17 : Input
Junction_2
    -> Junction_7

FME custom transformer CityGMLGeometrySetter

Parameters:
- GEOM =   # CityGML Lod Name
- ROLE =   # Feature Role

INPUT (input)
    -> AttributeCreator
AttributeCreator
    ATTR_TABLE:
      SET_TO citygml_lod_name = $(GEOM)
      SET_TO citygml_feature_role = $(ROLE)
    -> GeometryPropertySetter
GeometryPropertySetter
    OVERWRITE_CHOICE = Yes
    REMOVE_ATTRIBUTE = No
    SETTYPE_PARAM = Traits From Attributes
    SRC_ATTRS = citygml_lod_name
    SET -> OUTPUT (output)
OUTPUT (output)

FME custom transformer GetGrandParentID

Parameters:
- ATTR_TO_ENCODE =   # "" Source ID
- DEST_ATTR = gml_parent_id   # TYPE:varchar(200) Destination Attribute

Input (input)
    -> BinaryEncoder_3
BinaryEncoder_3
    ATTR_TO_ENCODE = $(ATTR_TO_ENCODE)
    DEST_ATTR = _parent_id
    ENCODING_TYPE = HEX
    -> VariableRetriever_5
VariableRetriever_5
    SCOPE = Global
    VALUE_ATTR = _gparent_id
    VARNAME = p@Value(_parent_id)
    -> BinaryDecoder
BinaryDecoder
    ATTR_ENCODING = utf-8
    ATTR_TO_DECODE = _gparent_id
    DEST_ATTR = $(DEST_ATTR)
    ENCODING_TYPE = HEX
    -> Output (output)
Output (output)

FME custom transformer ConvertGeometry

Parameters:
- IFC_UNIQUE_ID = @Value(ifc_unique_id)   # Ifc Unique Id

Input (input)
    -> GeometryPartExtractor_3
GeometryPartExtractor_3
    GQUERY:
      for $geom in //geometry
      where $geom/@fme_geometry_name = 'Body'
      return number($geom/@fme_id)
    EXTRACTED -> GeometryCoercer_3
GeometryCoercer_3
    GQUERY:
      for $geom in //geometry
      where $geom/@fme_geometry_type = 'IFMEExtrusion'
      or $geom/@fme_geometry_type = 'IFMEBRepSolid'
      return number($geom/@fme_id)
    KIND = fme_composite_surface
    COERCED -> Deaggregator
    UNTOUCHED -> Deaggregator
Deaggregator
    EXPLODE_INSTANCES = Yes
    GEOM_NAME_FIELD = _geometry_name
    LIST_ATTR_MODE_LOOKUP = LEAN
    MODE = Flatten All Levels
    SPLIT_COMPOSITES = No
    DEAGGREGATED -> Aggregator
Aggregator
    ACCUM_ATTRS_NAME = Merge Incoming Attributes
    AGGREGATE_TYPE = Homogeneous Collection (If Possible)
    GROUP_BY = ifc_unique_id
    MODE = Geometry - Assemble One Level
    ORDERED = No
    SEP = ,
    AGGREGATE -> GeometryRefiner_3
GeometryRefiner_3
    -> Output (output)
Output (output)
